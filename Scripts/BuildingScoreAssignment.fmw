FME workspace BuildingScoreAssignment.fmw

Parameters:
- SourceDataset_ARCGIS_LAYER = F:\Vancouver\481\Vancouver\rmsi data\buildings\Vancouver_buildings.shp   # Source Esri ArcGIS Layer
- SourceDataset_ARCGIS_LAYER_3 = F:\Vancouver\481\Vancouver\Vancouver_Feb2010\City streets data package\public_streets.shp   # Source Esri ArcGIS Layer
- DestDataset_SHAPE = N:\Geog 481\Test   # Destination Esri Shape Folder

Readers:
- ARCGIS_LAYER_1: ARCGIS_LAYER from $(SourceDataset_ARCGIS_LAYER)
- ARCGIS_LAYER_2: ARCGIS_LAYER from $(SourceDataset_ARCGIS_LAYER_3)

Writers:
- SHAPE_1: SHAPE to $(DestDataset_SHAPE)

Vancouver_buildings (reader ARCGIS_LAYER_1)
    attributes: FID integer, LAYER char(254), HEIGHT double
    -> TestFilter
TestFilter
    TEST_LIST:
      BOOL_OP,OR,COMPOSITE_TEST,<Unused>,TEST_CLAUSE,"TEST @Value(HEIGHT) <= 10",@Value(HEIGHT) < 10,BOOL_OP,AND,COMPOSITE_TEST,<Unused>,TEST_CLAUSE,"TEST @Value(HEIGHT) > 10
      TEST @Value(HEIGHT) <= 40",@Value(HEIGHT) > 10
    DEFAULT_VALUE = <UNFILTERED>
    <UNFILTERED> -> AttributeCreator_3
    @Value(HEIGHT) < 10 -> AttributeCreator
    @Value(HEIGHT) > 10 -> AttributeCreator_2
AttributeCreator
    ATTR_LIST = Score,1
    -> Bufferer
AttributeCreator_2
    ATTR_LIST = Score,1.15
    -> Bufferer
AttributeCreator_3
    ATTR_LIST = Score,1.30
    -> Bufferer
Bufferer
    INTERP_SEGMENTS = 8
    OFFSET = 50
    CAP_STYLE = Round
    BUFFERED -> SpatialRelator [input 2]
public_streets (reader ARCGIS_LAYER_2)
    attributes: FID integer, USE char(20), HBLOCK char(102)
    -> AttributeCreator_4
Note: Assign dummy time constant to streets. This is done because we have no current time score.
AttributeCreator_4
    ATTR_LIST = Time ,50
    -> SpatialFilter [input 2] [off]
    -> SpatialRelator [input 1]
SpatialRelator
    CURVE_BOUNDARY_RULE_PARAM = Default Rule
    LIST_NAME = _relationships
    SUCCESS_ATTR = _related_candidates
    PREDICATES = INTERSECTS
    CALC_CARD = No
    -> ListRangeExtractor
ListRangeExtractor
    SRC_LIST = _relationships{}.Score
    MIN = minScore
    MAX = maxScore
    -> Tester
Tester
    TEST_CLAUSE = TEST @Value(_related_candidates) > 0
    TEST_DESCRIPTION = ""
    TEST_MODE = Automatic
    BOOL_OP = OR
    PASSED -> ExpressionEvaluator
SpatialFilter
    PREDATTR = _predicate
    USE_BOUNDING_BOX = No
    PREDICATE_VALUE = Intersects
    BASE_TYPE = Multiple Filters
    CURVE_BOUNDARY_RULE_PARAM = Default Rule
    PASS_CRITERIA = Pass Against One Filter
    MERGE_ATTRS = Yes
    PASSED -> ExpressionEvaluator [off]
ExpressionEvaluator
    ATTRLIST = "Time "
    EXPRESSION = @Value(Time ) * @Value(maxScore)
    ACTION = Overwrite Existing Attributes
    -> public_streets (writer SHAPE_1)
public_streets (writer SHAPE_1)
    attributes: FID number(11,0), USE char(20), HBLOCK char(102), Time_ char(200), _predicate char(200), LAYER char(254), HEIGHT number(31,15), Score char(200), maxScore char(200), minScore char(200)
Inspector
