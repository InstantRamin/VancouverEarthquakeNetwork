FME workspace Density.fmw

Parameters:
- SourceDataset_SHAPE = /Volumes/STORE N GO/Vancouver/481/Vancouver/Vancouver_Dec2009/streetLighting ata package/SL_NODE_LBL_point.shp   # Source Esri Shape File(s)
- SourceDataset_SHAPE_3 = /Volumes/STORE N GO/Vancouver/481/Vancouver/Vancouver_Feb2010/City streets data package/public_streets.shp   # Source Esri Shape File(s)

Readers:
- SHAPE_1: SHAPE from $(SourceDataset_SHAPE)
- SHAPE_2: SHAPE from $(SourceDataset_SHAPE_3)

SL_NODE_LBL_point (reader SHAPE_1)
    attributes: LABEL char(254)
    -> Bufferer
    -> PointOnAreaOverlayer [input 1]
Note: Set a specified buffer around all point features
Bufferer
    INTERP_SEGMENTS = 8
    OFFSET = 15
    CAP_STYLE = Round
    BUFFERED -> PointOnAreaOverlayer [input 2]
Note: Check the count of the intersections occuring between points and the point's buffer
PointOnAreaOverlayer
    OV_ATTR = _overlaps
    POLYS_FIRST = No
    ATTR_ACCUM_MODE = Merge Incoming
    ATTR_CONFLICT_RES = Use Original
    POINT -> TestFilter
TestFilter
    TEST_LIST:
      BOOL_OP,AND,COMPOSITE_TEST,<Unused>,TEST_CLAUSE,"TEST @Value(_overlaps) != 1
      TEST @Value(_overlaps) < 3",@Value(_overlaps) != 1,BOOL_OP,AND,COMPOSITE_TEST,<Unused>,TEST_CLAUSE,"TEST @Value(_overlaps) > 3",@Value(_overlaps) > 3
    DEFAULT_VALUE = <UNFILTERED>
    @Value(_overlaps) != 1 -> AttributeCreator
    @Value(_overlaps) > 3 -> AttributeCreator_2
AttributeCreator
    ATTR_LIST = score,2
    -> SpatialRelator_2 [input 2]
    -> Inspector_3
AttributeCreator_2
    ATTR_LIST = score,4
    -> SpatialRelator_2 [input 2]
    -> Inspector_3
Intersector
    OV_ATTR = _overlaps
    SEPARATE_COLLINEAR_SEGMENTS = No
    PERFORM_SELF_INTERSECTION = No
    SEG_ATTR = _segments
    DUPLICATE_Z_NODES = No
SpatialRelator
    CALC_CARD = No
    SUCCESS_ATTR = _related_candidates
    CURVE_BOUNDARY_RULE_PARAM = Default Rule
    LIST_NAME = _relationships
Note: Import Street data to transfer scores to
public_streets (reader SHAPE_2)
    attributes: USE char(20), HBLOCK char(102)
    -> Bufferer_2
Bufferer_2
    INTERP_SEGMENTS = 8
    OFFSET = 50
    CAP_STYLE = Round
    BUFFERED -> SpatialRelator_2 [input 1]
SpatialRelator_2
    CALC_CARD = No
    SUCCESS_ATTR = _related_candidates
    CURVE_BOUNDARY_RULE_PARAM = Default Rule
    PREDICATES = INTERSECTS OVERLAPS
    LIST_NAME = _relationships
    -> ListRangeExtractor
Note: Apply the max score to the road buffer
ListRangeExtractor
    SRC_LIST = _relationships{}.score
    MIN = minScore
    MAX = maxScore
    -> Inspector_3
Inspector_3
